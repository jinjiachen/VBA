Attribute VB_Name = "ThisDrawing"
Attribute VB_Base = "0{D70E31AD-2614-49F2-B0FC-ACA781D81F3E}"
Attribute VB_GlobalNameSpace = False
Attribute VB_Creatable = False
Attribute VB_PredeclaredId = True
Attribute VB_Exposed = True
Attribute VB_TemplateDerived = False
Attribute VB_Customizable = True

Public Sub TestCirlce()
Dim pt1, pt2, pt3 As Variant
Dim radius As Double
pt1 = ThisDrawing.Utility.GetPoint(, "指定圆心")
radius = ThisDrawing.Utility.GetReal("请输入半径")
AddCircle pt1, radius

pt1 = ThisDrawing.Utility.GetPoint(, "指定圆心")
radius = ThisDrawing.Utility.GetReal("请输入直径")
AddCircleCD pt1, radius


pt1 = ThisDrawing.Utility.GetPoint(, "输入第一点")
pt2 = ThisDrawing.Utility.GetPoint(pt1, "输入第二点")
AddCircle2P pt1, pt2

pt1 = ThisDrawing.Utility.GetPoint(, "输入第一点")
pt2 = ThisDrawing.Utility.GetPoint(pt1, "输入第二点")
pt3 = ThisDrawing.Utility.GetPoint(pt2, "输入第三点")
AddCircle3P pt1, pt2, pt3
End Sub

Attribute VB_Name = "模块1"

Public Function AddCircle(ByVal ptCen As Variant, ByVal radius As Variant) As AcadCircle
Dim objCir As AcadCircle
Set objCir = ThisDrawing.ModelSpace.AddCircle(ptCen, radius)
Set AddCircle = objCir
End Function

Public Function AddCircleCD(ByVal ptCen As Variant, ByVal diameter As Variant) As AcadCircle
Dim objCir As AcadCircle
Set objCir = ThisDrawing.ModelSpace.AddCircle(ptCen, diameter / 2)
Set AddCircleCD = objCir
End Function

Public Function AddCircle2P(ByVal pt1 As Variant, ByVal pt2 As Variant) As AcadCircle
Dim ptCen(2) As Double
Dim diameter As Double
Dim objCir As AcadCircle
ptCen(0) = (pt1(0) + pt2(0)) / 2
ptCen(1) = (pt1(1) + pt2(1)) / 2
ptCen(2) = 0
diameter = Sqr((pt2(0) - pt1(0)) ^ 2 + (pt2(1) - pt1(1)) ^ 2)
Set objCir = ThisDrawing.ModelSpace.AddCircle(ptCen, diameter / 2)
Set AddCircle2P = objCir
End Function

Public Function AddCircle3P(ByVal pt1 As Variant, ByVal pt2 As Variant, ByVal pt3 As Variant) As AcadCircle
Dim xysm, xyse, xy As Double
Dim ptCen(2) As Double
Dim diameter As Double
Dim objCir As AcadCircle
xy = pt1(0) ^ 2 + pt1(1) ^ 2
xyse = xy - pt3(0) ^ 2 - pt3(1) ^ 2
xysm = xy - pt2(0) ^ 2 - pt2(1) ^ 2
xy = (pt1(0) - pt2(0)) * (pt1(1) - pt3(1)) - (pt1(0) - pt3(0)) * (pt1(1) - pt2(1))
If Abs(xy) < 0.00000001 Then
    MsgBox "不能创建圆"
    Exit Function
End If
ptCen(0) = (xysm * (pt1(1) - pt3(1)) - xyse * (pt1(1) - pt2(1))) / (2 * xy)
ptCen(1) = (xyse * (pt1(0) - pt2(0)) - xysm * (pt1(0) - pt3(0))) / (2 * xy)
ptCen(2) = 0
radius = Sqr((pt1(0) - ptCen(0)) * (pt1(0) - ptCen(0)) + (pt1(1) - ptCen(1)) ^ 2)
If radius < 0.000001 Then
    MsgBox "半径过小"
    Exit Function
End If
Set objCir = ThisDrawing.ModelSpace.AddCircle(ptCen, radius)
Set AddCircle3P = objCir
End Function
