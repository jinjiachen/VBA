Attribute VB_Name = "ThisDrawing"
Attribute VB_Base = "0{D70E31AD-2614-49F2-B0FC-ACA781D81F3E}"
Attribute VB_GlobalNameSpace = False
Attribute VB_Creatable = False
Attribute VB_PredeclaredId = True
Attribute VB_Exposed = True
Attribute VB_TemplateDerived = False
Attribute VB_Customizable = True

Public Sub TestText()
Dim ptinsert(2) As Double
ptinsert(0) = 100: ptinsert(1) = 100: ptinsert(2) = 0
AddText "AutoCAD 2010", ptinsert, 5


ptinsert(0) = 100: ptinsert(1) = 110: ptinsert(2) = 0
AddMtext ptinsert, 30, "VBA 程序设计"


ptinsert(0) = 100: ptinsert(1) = 120: ptinsert(2) = 0
AddTextHA "清华大学出版社", ptinsert, 5, 0.4


ptinsert(0) = 100: ptinsert(2) = 140: ptinsert(2) = 0
AddMtextHA ptinsert, 50, "明经通道欢迎你", 5, 0.4


End Sub

Attribute VB_Name = "模块1"

Public Function AddText(ByVal text As String, ByVal ptinsert As Variant, ByVal height As Double) As AcadText
Set AddText = ThisDrawing.ModelSpace.AddText(text, ptinsert, height)
End Function

Public Function AddTextHA(ByVal text As String, ByVal ptinsert As Variant, ByVal height As Double, ByVal angle As Double) As AcadText
Dim objText As AcadText
Set objText = ThisDrawing.ModelSpace.AddText(text, ptinsert, height)
objText.Rotate ptinsert, angle
objText.Update
Set AddTextHA = objText
End Function

Public Function AddMtext(ByVal ptinsert As Variant, ByVal width As Double, ByVal text As String) As AcadMText
Set AddMtext = ThisDrawing.ModelSpace.AddMtext(ptinsert, width, text)

End Function

Public Function AddMtextHA(ByVal ptinsert As Variant, ByVal width As Double, ByVal text As String, ByVal height As Double, ByVal angle As Double) As AcadMText
Dim objMtext As AcadMText
Set objMtext = ThisDrawing.ModelSpace.AddMtext(ptinsert, width, text)
objMtext.height = height
objMtext.Rotation = angle
Set AddMtextHA = objMtext
End Function
