Attribute VB_Name = "ThisDrawing"
Attribute VB_Base = "0{D70E31AD-2614-49F2-B0FC-ACA781D81F3E}"
Attribute VB_GlobalNameSpace = False
Attribute VB_Creatable = False
Attribute VB_PredeclaredId = True
Attribute VB_Exposed = True
Attribute VB_TemplateDerived = False
Attribute VB_Customizable = True
Sub Myaddline()
Dim ln As AcadLine
Dim startPT(2) As Double, endPT(2) As Double
startPT(0) = 0
startPT(1) = 1
startPT(0) = 100
startPT(1) = 50
Set ln = ThisDrawing.ModelSpace.AddLine(startPT(), endPT())
ln.Color = acRed
ZoomAll

End Sub
