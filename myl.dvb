Attribute VB_Name = "Module1"
Sub myl()
Dim p(0 To 10000) As Double
Dim ln As Object
j = -1
For i = 0 To 50 Step 0.1
    j = j + 1
    p(j) = i
    j = j + 1
    p(j) = 2 * i * i
Next i
ThisDrawing.ModelSpace.AddLightWeightPolyline (p)
End Sub
