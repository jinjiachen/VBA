Attribute VB_Name = "ThisDrawing"
Attribute VB_Base = "0{D70E31AD-2614-49F2-B0FC-ACA781D81F3E}"
Attribute VB_GlobalNameSpace = False
Attribute VB_Creatable = False
Attribute VB_PredeclaredId = True
Attribute VB_Exposed = True
Attribute VB_TemplateDerived = False
Attribute VB_Customizable = True

Public Sub TestDim()
'起始点位置
Dim pt1(2) As Double
pt1(0) = 200: pt1(1) = 160: pt1(2) = 0

'根据相对坐标计算其它点的位置
Dim pt2, pt3, pt4, pt5 As Variant
pt2 = GetPoint(pt1, -40, 0)
pt3 = GetPoint(pt2, 7 * PI / 6, 20)
pt4 = GetPoint(pt3, 6, -10)
pt5 = GetPoint(pt1, 0, -20)

'绘制外轮廓线
ThisDrawing.ModelSpace.AddLine pt1, pt2
ThisDrawing.ModelSpace.AddLine pt2, pt3
ThisDrawing.ModelSpace.AddLine pt3, pt4
ThisDrawing.ModelSpace.AddLine pt4, pt5
ThisDrawing.ModelSpace.AddLine pt5, pt1

'绘制图形
Dim ptCen1, ptCen2 As Variant
ptCen1 = GetPoint(pt3, 16, 0)
ptCen2 = GetPoint(ptCen1, 25, 0)
ThisDrawing.ModelSpace.AddCircle ptCen1, 3
ThisDrawing.ModelSpace.AddCircle ptCen2, 4


Dim ptTemp1, ptTemp2 As Variant
'水平标注
ptTemp1 = GetPoint(pt1, -20, 3)
AddDimRotated pt1, pt2, ptTemp1, 0
'垂直标注
ptTemp1 = GetPoint(pt1, 4, 10)
AddDimRotated pt1, pt5, ptTemp1, PI / 2
'旋转标注
ptTemp1 = GetPoint(pt3, -3, -6)
AddDimRotated pt3, pt4, ptTemp1, 7 * PI / 4
'对齐标注
ptTemp1 = GetPoint(pt2, -3, 4)
AddDimAlignedCTXT pt2, pt3, ptTemp1, "new position", 4, 10
'角度标注
ptTemp1 = GetPoint(pt5, -5, 5)
AddDimAngular pt5, pt1, pt4, ptTemp1
'半径标注
ptTemp1 = GetPoint(ptCen1, PI / 4, 3)
AddDimRadial ptCen1, ptTemp1, -3
'直径标注
ptTemp1 = GetPoint(ptCen2, PI / 4, 4)
ptTemp2 = GetPoint(ptCen2, PI / 4, -4)
AddDimDiametric ptTemp2, ptTemp2, 0
'坐标标注
AddDimOrdStandard ptCen2, 10, -10

End Sub

Attribute VB_Name = "模块1"

Public Function AddDimAligned(ByVal pt1 As Variant, ByVal pt2 As Variant, ByVal ptText As Variant) As AcadDimAligned
Set AddDimAligned = ThisDrawing.ModelSpace.AddDimAligned(pt1, pt2, ptText)
End Function

Public Function AddDimAlignedCTXT(ByVal pt1 As Variant, ByVal pt2 As Variant, ByVal ptText As Variant, ByVal text As String, Optional x As Double = 0, Optional y As Double = 0) As AcadDimAligned
Dim objDim As AcadDimAligned
Set objDim = AddDimAligned(pt1, pt2, ptText)
objDim.TextOverride = text

'移动文字前，需先指定尺寸线的变化情况
objDim.TextMovement = acMoveTextAddLeader
ptText(0) = ptText(0) + x
ptText(1) = ptText(1) + y
objDim.TextPosition = ptText

objDim.Update
Set adddimalighnedctxt = objDim
End Function

Public Function AddDimRotated(ByVal pt1 As Variant, ByVal pt2 As Variant, ByVal ptText As Variant, ByVal angle As Double) As AcadDimRotated
Set AddDimRotated = ThisDrawing.ModelSpace.AddDimRotated(pt1, pt2, ptText, angle)
End Function

Public Function AddDimRotatedCTXT(ByVal pt1 As Variant, ByVal pt2 As Variant, ByVal ptText As Variant, ByVal angle As Double, ByVal text As String) As AcadDimRotated
Dim objDim As AcadDimRotated
Set objDim = AddDimRotated(pt1, pt2, ptText, angle, text)
objDim.TextOverride = text
Set addimrotatedctxt = objDim
End Function

Public Function AddDimRadial(ByVal ptCen As Variant, ByVal ptChord As Variant, ByVal leaderLength As Double) As AcadDimRadial
Set AddDimRadial = ThisDrawing.ModelSpace.AddDimRadial(ptCen, ptChord, leaderLength)
End Function

Public Function AddDimRadialAR(ByVal ptCen As Variant, ByVal radius As Double, ByVal angle As Double, Optional leaderLength As Double = 5) As AcadDimRadial
Dim ptChord As Variant
ptChord = GetPointAR(ptCen, angle, radius)
Set AddDimRadialAR = AddDimRadial(ptCen, ptChord, leaderLength)
End Function

Public Function AddDimDiametric(ByVal ptChord1 As Variant, ByVal ptChord2 As Variant, ByVal leaderLength As Double) As AcadDimDiametric
Set AddDimDiametric = ThisDrawing.ModelSpace.AddDimDiametric(ptChord1, ptChord2, leaderLength)
End Function

Public Function AddDimDiametricAR(ByVal ptCen As Variant, ByVal radius As Double, ByVal angle As Double, Optional leaderLength As Double = 5) As AcadDimDiametric
Dim ptChord1, ptChord2 As Variant
ptChord1 = GetPointAR(ptCen, angle, radius)
ptChord2 = GetPointAR(ptCen, angle + PI, radius)
Set AddDimDiametricAR = AddDimDiametric(ptChord1, ptChord2, leaderLength)
End Function

Public Function AddDimAngular(ByVal ptVertex As Variant, ByVal ptSt As Variant, ByVal ptEn As Variant, ByVal ptText As Variant) As AcadDimAngular
Set AddDimAngular = ThisDrawing.ModelSpace.AddDimAngular(ptVertex, ptSt, ptEn, ptText)
End Function

Public Function AddDimAngularPO(ByVal ptVertex As Variant, ByVal ptSt As Variant, ByVal ptEn As Variant, Optional offset As Double = 5) As AcadDimAngular
Dim ptTemp As Variant
Dim angle, radius As Double

'尺寸文字放在起点和终点的中心线上,如果0度介于起始角度和终止角度之间，计算方法要调整
If getanglefromx(ptVertex, ptEn) < getanglefromx(ptVertex, ptSt) Then
    angle = (2 * PI - getanglefromx(ptVertex, ptSt) + getanglefromx(ptVertex, ptEn)) / 2
Else
    angle = (getanglefromx(ptVertex, ptEn) - getanglefromx(ptVertex, ptSt)) / 2
End If
'以起点作为圆弧上的点来计算半径
radius = GetDistance(ptVertex, ptSt)

'offset是超出圆弧的距离
ptTemp = GetPointAR(ptVertex, angle, radius + offset)
Set AddDimAngularPO = AddDimAngular(ptVertex, ptSt, ptEn, ptTemp)

End Function

Public Function AddDimOrdinate(ByVal ptDef As Variant, ByVal ptText As Variant, ByVal xAxis As Boolean) As AcadDimOrdinate
Set AddDimOrdinate = ThisDrawing.ModelSpace.AddDimOrdinate(ptDef, ptText, xAxis)
End Function

Public Function AddDimOrdinateXY(ByVal ptDef As Variant, ByVal ptTextX As Variant, ByVal ptTextY As Variant)
ThisDrawing.ModelSpace.AddDimOrdinate ptDef, ptTextX, True
ThisDrawing.ModelSpace.AddDimOrdinate ptDef, ptTextY, False
End Function

Public Function AddDimOrdStandard(ByVal ptDef As Variant, ByVal x1 As Double, ByVal y2 As Double, Optional y1 As Double = 0, Optional x2 As Double = 0)
Dim ptTextX(2) As Double
Dim ptTextY(2) As Double

'为两个文字位置定义点位置
ptTextX(0) = ptDef(0) + x2: ptTextX(1) = ptDef(1) + y2: ptTextX(2) = 0
ptTextY(0) = ptDef(0) + x1: ptTextY(1) = ptDef(1) + y1: ptTextY(2) = 0

AddDimOrdinateXY ptDef, ptTextX, ptTextY
End Function
Public Function GetPoint(pt As Variant, x As Double, y As Double) As Variant
Dim ptTarget(2) As Double
ptTarget(0) = pt(0) + x
ptTarget(1) = pt(1) + y
ptTarget(2) = 0
GetPoint = ptTarget
End Function

Public Function GetPointAR(ByVal ptBase As Variant, ByVal angle As Double, ByVal length As Double) As Variant
Dim pt(2) As Double
pt(0) = ptBase(0) + length * Cos(angle)
pt(1) = ptBase(1) + length * Sin(angle)
pt(2) = ptBase(2)
GetPointAR = pt
End Function
