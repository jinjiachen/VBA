Attribute VB_Name = "ThisDrawing"
Attribute VB_Base = "0{D70E31AD-2614-49F2-B0FC-ACA781D81F3E}"
Attribute VB_GlobalNameSpace = False
Attribute VB_Creatable = False
Attribute VB_PredeclaredId = True
Attribute VB_Exposed = True
Attribute VB_TemplateDerived = False
Attribute VB_Customizable = True

Public Sub TestArc()
'1
Dim ptCen(2) As Double
ptCen(0) = 100: ptCen(1) = 100: ptCen(2) = 0

Dim objArc1 As AcadArc
Set objArc1 = AddArcCSEA(ptCen, 50, 0.8, 2.3)

'2
ptCen(0) = 100: ptCen(1) = 90: ptCen(2) = 0
Dim objArc2 As AcadArc
Set objArc2 = AddArcCSEP(ptCen, objArc1.StartPoint, objArc1.EndPoint)

'3
Dim objArc3 As AcadArc
Set objArc3 = AddArcCSPA(ptCen, objArc1.EndPoint, 2)

'4
Dim pt1(2) As Double
pt1(0) = 140: pt1(1) = 60: pt1(2) = 0
Dim objArc4 As AcadArc
Set objArc4 = AddArc3Pt(objArc3.EndPoint, pt1, objArc2.StartPoint)

'5
Dim pt2(2) As Double
pt2(0) = 70: pt2(1) = 100: pt2(2) = 0
Dim objArc5 As AcadArc
Set objArc5 = AddArcCSPL(ptCen, pt2, 30)
ZoomAll
End Sub

Attribute VB_Name = "模块1"

Public Function AddArcCSEA(ByVal ptCen As Variant, ByVal radius As Double, ByVal stAng As Double, ByVal enAng As Double) As AcadArc
On Error GoTo errHandle

Dim objArc As AcadArc
Set objArc = ThisDrawing.ModelSpace.AddArc(ptCen, radius, stAng, enAng)
objArc.Color = acBlue
objArc.Update
Set AddArcCSEA = objArc
Exit Function
errHandle:
    MsgBox Err.Description
End Function

Public Function AddArcCSEP(ByVal ptCen As Variant, ByVal ptSt As Variant, ByVal ptEn As Variant) As AcadArc
Dim objArc As AcadArc
Dim radius As Double
Dim stAng As Double
Dim enAng As Double
radius = GetDistance(ptCen, ptSt)
stAng = ThisDrawing.Utility.AngleFromXAxis(ptCen, ptSt)
enAng = ThisDrawing.Utility.AngleFromXAxis(ptCen, ptEn)
Set objArc = ThisDrawing.ModelSpace.AddArc(ptCen, radius, stAng, enAng)
objArc.Color = acCyan
objArc.Update
Set AddArcCSEP = objArc
End Function

Public Function GetDistance(ByVal sp As Variant, ByVal ep As Variant) As Double
Dim x, y, z As Double
x = sp(0) - ep(0)
y = sp(1) - ep(1)
z = sp(2) - ep(2)
GetDistance = Sqr((x ^ 2) + (y ^ 2) + (z ^ 2))
End Function

Public Function AddArcCSPA(ByVal ptCen As Variant, ByVal ptSt As Variant, ByVal angle As Double) As AcadArc
Dim objArc As AcadArc
Dim radius As Double
Dim ptEn As Variant
Dim angTemp As Double
angTemp = ThisDrawing.Utility.AngleFromXAxis(ptCen, ptSt)
angTemp = angTemp + angle
radius = GetDistance(ptCen, ptSt)
ptEn = ThisDrawing.Utility.PolarPoint(ptCen, angTemp, radius)
Set objArc = AddArcCSEP(ptCen, ptSt, ptEn)
objArc.Color = acRed
objArc.Update
Set AddArcCSPA = objArc
End Function

Public Function AddArc3Pt(ByVal ptSt As Variant, ByVal ptSc As Variant, ByVal ptEn As Variant) As AcadArc
Dim objArc As AcadArc
Dim ptCen As Variant
Dim radius As Double
ptCen = GetCenOf3Pt(ptSt, ptSc, ptEn, radius)
Set objArc = AddArcCSEP(ptCen, ptSt, ptEn)
objArc.Color = acGreen
objArc.Update
Set AddArc3Pt = objArc
End Function

Public Function GetCenOf3Pt(pt1 As Variant, pt2 As Variant, pt3 As Variant, ByRef radius As Double) As Variant
Dim xysm, xyse, xy As Double
Dim ptCen(2) As Double
xy = pt1(0) ^ 2 + pt1(1) ^ 2
xyse = xy - pt3(0) ^ 2 - pt3(1) ^ 2
xysm = sy - pt2(0) ^ 2 - pt2(1) ^ 2
xy = (pt1(0) - pt2(0)) * (pt1(1) - pt3(1)) - (pt1(0) - pt3(0)) * (pt1(1) - pt2(1))

If Abs(xy) < 0.0000001 Then
    MsgBox "无法创建圆形"
    Exit Function
End If
ptCen(0) = (xysm * (pt1(1) - pt3(1)) - xyse * (pt1(1) - pt2(1))) / (2 * xy)
ptCen(1) = (xyse * (pt1(0) - pt2(0)) - xysm * (pt1(0) - pt3(0))) / (2 * xy)
ptCen(2) = 0
radius = Sqr((pt1(0) - ptCen(0)) * (pt1(0) - ptCen(0)) + (pt1(1) - ptCen(1)) * (pt1(1) - ptCen(1)))
If radius < 0.0000001 Then
    MsgBox "半径过小"
    Exit Function
End If
GetCenOf3Pt = ptCen
End Function

Public Function AddArcCSPL(ByVal ptCen As Variant, ByVal ptSt As Variant, ByVal length As Double) As AcadArc
Dim objArc As AcadArc
Dim radius, angle As Double

radius = GetDistance(ptCen, ptSt)
angle = length / radius
Set objArc = AddArcCSPA(ptCen, ptSt, angle)
objArc.Color = acMagenta
objArc.Update
Set AddArcCSPL = objArc
End Function
