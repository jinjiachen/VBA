Attribute VB_Name = "模块1"

Public Function GetPoint(pt As Variant, x As Double, y As Double) As Variant
Dim ptTarget(2) As Double
ptTarget(0) = pt(0) + x
ptTarget(1) = pt(1) + y
ptTarget(2) = 0
GetPoint = ptTarget
End Function

Public Function GetPointAR(ByVal ptBase As Variant, ByVal angle As Double, ByVal length As Double) As Variant
Dim pt(2) As Double
pt(0) = ptBase(0) + length * Cos(angle)
pt(1) = ptBase(1) + length * Sin(angle)
pt(2) = ptBase(2)
GetPointAR = pt
End Function

Public Function GetMidPt(pt1 As Variant, pt2 As Variant) As Variant
Dim ptMid(2) As Double
ptMid(0) = (pt1(0) + pt2(0)) / 2
ptMid(1) = (pt1(1) + pt2(1)) / 2
ptMid(2) = 0
GetMidPt = ptMid
End Function

Public Function GetDistance(ptSt As Variant, ptEn As Variant) As Double
Dim x, y, z As Double
x = ptSt(0) - ptEn(0)
y = ptSt(1) - ptEn(1)
z = ptSt(2) - ptEn(2)
GetDistance = Sqr(x ^ 2 + y ^ 2 + z ^ 2)
End Function

Public Function GetDisPtToLine(ByVal pt As Variant, a As Double, b As Double, c As Double) As Double
Dim d As Double
d = Sqr(a * a + b * b)

If d < 0.0000001 Then
    GetDisPtToLine = 1E+20
Else
    GetDisPtToLine = (a * pt(0) + b * pt(1) + c) / d
End If
End Function

Public Function GetAngleFromX(ByVal ptSt As Variant, ByVal ptEn As Variant) As Double
GetAngleFromX = ThisDrawing.Utility.AngleFromXAxis(ptSt, ptEn)
End Function

Public Function MinDouble(ByVal a As Double, ByVal b As Double) As Double
If a > b Then
    MinDouble = b
Else
    MinDouble = a
End If
End Function

Public Function MaxDouble(ByVal a As Double, ByVal b As Double) As Double
If a > b Then
    MaxDouble = a
Else
    MaxDouble = b
End If
End Function

Public Function Intersect2Line(ByVal objLine1 As AcadLine, ByVal objLine2 As AcadLine, ByRef pt As Variant) As Boolean
Dim ptTemp As Variant
ptTemp = objLine1.IntersectWith(objLine2, acExtendBoth)

'如果直线不相交,ptTemp就为空
If ptTemp Is Empty Then
    Intersect2Line = False
Else
    Intersect2Line = True
End If
End Function
