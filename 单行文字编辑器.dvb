Attribute VB_Name = "frmMain"
Attribute VB_Base = "0{92CDE0DE-87AB-43CE-A7E3-C8B6BCA4D742}{0D219777-3A5A-4490-A750-F7CE57057F31}"
Attribute VB_GlobalNameSpace = False
Attribute VB_Creatable = False
Attribute VB_PredeclaredId = True
Attribute VB_Exposed = False
Attribute VB_TemplateDerived = False
Attribute VB_Customizable = False
Private Sub chcColor_Click()
Dim color As Integer

'选择颜色
If chcColor.Value = True Then
    color = 模块1.GetColorFromDLG(1, True, 256)
    txtColor.Text = color
End If


Call 模块1.OptionButtonsOff

If txtColor.Enabled = False Then
    txtColor.Enabled = True
Else
    txtColor.Enabled = False
End If

End Sub

Private Sub chcHeight_Click()
Call 模块1.OptionButtonsOff
'切换文字框的可用状态
If txtHeight.Enabled = False Then
    txtHeight.Enabled = True
    
    
    frmMain.txtHeight.SetFocus
    '从第一个字符开始
    frmMain.txtHeight.SelStart = 0
    '选择文字框所有的文字内容
    frmMain.txtHeight.SelLength = Len(frmMain.txtHeight.Text)
Else
    txtHeight.Enabled = False
End If

End Sub

Private Sub chcLayer_Click()
Call 模块1.OptionButtonsOff

'切换对应组合框的可用状态
If cboLayer.Enabled = False Then
    cboLayer.Enabled = True
Else
    cboLayer.Enabled = False
End If

End Sub

Private Sub cmdAll_Click()
Dim FilterSet As Object
'错误处理
On Error GoTo errControl

frmMain.Hide

Set FilterSet = ThisDrawing.SelectionSets.Add("Example")

'定义过滤规则
Dim filterType(0) As Integer
Dim filterData(0) As Variant
filterType(0) = 0
filterData(0) = "TEXT"
FilterSet.Select acSelectionSetAll, , , filterType, filterData

Dim FilterEnt As Object

'全局修改文字特性
For Each FilterEnt In FilterSet
'高度
If chcHeight.Value = True Then FilterEnt.Height = txtHeight.Text

'图层和颜色
If chcLayer.Value = True Then
    FilterEnt.Layer = cboLayer.Text
    FilterEnt.color = acByLayer
End If

'文字
If chcStyle.Value = True Then
    FilterEnt.StyleName = cboStyle.Text
End If


'颜色
If chcColor.Value = True Then FilterEnt.color = txtColor.Text

FilterEnt.Update
Next FilterEnt

ThisDrawing.SelectionSets("Example").Delete
frmMain.Show

'定义错误控制
errControl:
'删除选择集
ThisDrawing.SelectionSets("Example").Delete

'如果用户按下了ESC鍵
If CheckKey(VK_ESCAPE) = True Then
    End
Else
'肯定是另一种类型的错误
    MsgBox Err.Description
End If
End Sub

Private Sub cmdCancel_Click()
End
End Sub

Private Sub cmdReset_Click()
'重置控件的状态
chcHeight.Value = False
chcLayer.Value = False
chcStyle.Value = False
chcColor.Value = False
chcHeight.Enabled = True
chcLayer.Enabled = True
chcColor.Enabled = True
chcStyle.Enabled = True


optLocation.Enabled = True
optAngle.Enabled = True
optRotate.Enabled = True
optEdit.Enabled = True
optLocation.Value = False
optAngle.Value = False
optRotate.Value = False
optEdit.Value = False


'从系统变量中取值，恢复当前文字的设置
txtHeight.Text = ThisDrawing.GetVariable("textsize")
cboLayer.Text = ThisDrawing.GetVariable("clayer")
cboStyle.Text = ThisDrawing.GetVariable("textstyle")
txtColor.Value = "1"
txtColor.Enabled = False

cmdSelect.Enabled = False
cmdAll.Enabled = False
End Sub

Private Sub cmdSelect_Click()
Dim FilterSet As Object
'错误控制
On Error GoTo errControl

Set FilterSet = ThisDrawing.SelectionSets.Add("Example")

Dim filterType(0) As Integer
Dim filterData As Variant
'设置过滤类型
filterType(0) = 0
filterDate(0) = "TEXT"

frmMain.Hide

'使用过滤器，由用户在屏幕上选择文字
FilterSet.SelectOnScreen filterType, filterData

Dim FilterEnt As Object

For Each FilterEnt In FilterSet
    '对全局特性修改
    If chcHeight.Value = True Then FilterEnt.Height = txtHeight.Text
    If chcLayer.Value = True Then
        FilterEnt.Layer = cboLayer.Text
        filerent.color = acByLayer
    End If
    
    If chcStyle.Value = True Then FilterEnt.StyleName = cboStyle.Text
    If chcColor.Value = True Then FilterEnt.color = txtColor.Text
    
    '对单个或成组对象的修改
    If optLocation.Value = True Then
        Dim inPoint As Variant
        Dim oldPoint As Variant
        oldPoint = FilterEnt.InsertionPoint
        inPoint = ThisDrawing.Utility.GetPoint(oldPoint, "指定新的插入点:")
        FilterEnt.InsertionPoint = inPoint
    End If
    
    
    If optAngle.Value = True Then
        Dim inPoint1 As Variant
        inPoint1 = FilterEnt.InsertionPoint
        Dim retAngle As Double
        retAngle = ThisDrawing.Utility.GetAngle(, "文字倾斜角度:")
        FilterEnt.ObliqueAngle = reangle
    End If
    
    
    If optRotate.Value = True Then
        Dim inPoint2 As Variant
        inPoint2 = FilterEnt.InsertionPoint
        Dim retAngle1 As Double
        retAngle1 = ThisDrawing.Utility.GetAngle(inPoint2, "文字旋转角度:")
        FilterEnt.Rotation = retAngle1
    End If
    
    
    If optEdit.Value = True Then
        Dim retValue As String
        retValue = InputBox("输入新的文字内容:", "编辑文字内容", FilterEnt.TextString)
        FilterEnt.TextString = revalue
    End If
    
    FilterEnt.Update

Next FilterEnt

'删除选择集
ThisDrawing.SelectionSets("Example").Delete
frmMain.Show


    '定义错误控制语句
errControl:
    On Error Resume Next
    If Not IsNull(ThisDrawing.SelectionSets.Item("Example")) Then
        ThisDrawing.SelectionSets("Example").Delete
    End If
    '如果用户按下ESC，退出程序
    If CheckKey(VK_ESCAPE) = True Then
        End
    Else
        '描述错误类型
        MsgBox Err.Description
    End If
    
End Sub

Private Sub optAngle_Click()
Call 模块1.CheckButtonsOff
End Sub

Private Sub optEdit_Click()
Call 模块1.CheckButtonsOff
End Sub

Private Sub optLocation_Click()
Call 模块1.CheckButtonsOff
End Sub

Private Sub optRotate_Click()
Call 模块1.CheckButtonsOff
End Sub

Attribute VB_Name = "模块1"
Public Const VK_ESCAPE = &H1B
'该函数的作用是判断函数调用时指定虚拟鍵的状态
Declare Function GetAsyncKeyState Lib "user32" (ByVal vKey As Long) As Integer

Public Function CheckKey(lngKey As Long) As Boolean
If GetAsyncKeyState(lngKey) Then
    CheckKey = True
Else
    CheckKey = False
End If
End Function

Public Function OptionButtonsOff()
    '禁用所有的单选按钮，并对命令按钮的状态进行调整
    With frmMain
        .optLocation.Enabled = False
        .optAngle.Enabled = False
        .optRotate.Enabled = False
        .optEdit.Enabled = False
        .cmdAll.Enabled = True
        .cmdSelect.Enabled = True
        .cmdReset.Enabled = True
    End With
    
        
End Function
Option Explicit

'声明
Private Declare Function acedsetcolordialog Lib "acad.exe" _
    (color As Long, ByVal bAllowMetaColor As Boolean, ByVal nCurLayerColor As Long) As Boolean
    
'封闭API函数，获得用户选择颜色的结果
Public Function GetColorFromDLG(ByVal initColor As Long, _
    ByVal bAllowMetaColor As Boolean, ByVal nCurLayerColor As Long) As Long
    
    GetColorFromDLG = -1
    On Error Resume Next
    
    If acedsetcolordialog(initColor, bAllowMetaColor, nCurLayerColor) Then
        GetColorFromDLG = initColor
    End If
    
    
    End Function



Public Function CheckButtonsOff()
'禁用所有的复选框和控件，并对命令按钮的状态进行调整
With frmMain
    .chcHeight.Enabled = False
    .txtHeight.Enabled = False
    .chcLayer.Enabled = False
    .cboLayer.Enabled = False
    .chcStyle.Enabled = False
    .cboStyle.Enabled = False
    .chcColor.Enabled = False
    .txtColor.Enabled = False
    .cmdReset.Enabled = False
    .cmdAll.Enabled = True
    .cmdSelect.Enabled = True
End With

End Function
