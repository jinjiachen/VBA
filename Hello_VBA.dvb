Attribute VB_Name = "ThisDrawing"
Attribute VB_Base = "0{D70E31AD-2614-49F2-B0FC-ACA781D81F3E}"
Attribute VB_GlobalNameSpace = False
Attribute VB_Creatable = False
Attribute VB_PredeclaredId = True
Attribute VB_Exposed = True
Attribute VB_TemplateDerived = False
Attribute VB_Customizable = True

Public Sub HelloVBA()
Dim p(2) As Double
Dim value As Integer
p(0) = 100
p(1) = 100
p(2) = 0
value = MsgBox("Hello VBA" & vbNewLine & "是否在图形中添加?", vbYesNo, "获得用户选择")
If value = 6 Then
ThisDrawing.ModelSpace.AddText "Hello, VBA!", p, 10
End If

End Sub
