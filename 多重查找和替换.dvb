Attribute VB_Name = "Form1"
Attribute VB_Base = "0{9B6F71F9-A9E3-4643-85A2-C0CD8B7B707B}{E9557134-58CF-453A-B1AD-A0458915B138}"
Attribute VB_GlobalNameSpace = False
Attribute VB_Creatable = False
Attribute VB_PredeclaredId = True
Attribute VB_Exposed = False
Attribute VB_TemplateDerived = False
Attribute VB_Customizable = False


Public Sub UserForm_Initialize()
'清空所有的文字框
Dim txt As Control
For Each txt In Form1.Controls
    If TypeOf txt Is TextBox Then
        txt.Text = ""
    End If
Next
End Sub

Private Sub cmdApply_Click()
'定义变量和对象
Dim adText As AcadText
Dim adMText As AcadMText
Dim adSS As AcadSelectionSet
Dim fType(1) As Integer, fData(1)
Dim Misc1 As String
Dim MiscReplace1 As String
Dim Misc2 As String
Dim MiscReplace2 As String
Dim Misc3 As String
Dim MiscReplace3 As String
Dim intCnt As Integer

'获得替换数据
Misc1 = txtFind1.Text
MiscReplace1 = txtReplace1.Text
Misc2 = txtFind2.Text
MiscReplace2 = txtReplace2.Text
Misc3 = txtFind3.Text
MiscReplace3 = txtReplace3.Text

On Error Resume Next
Form1.Hide  '隐藏窗口，获得焦点
'创建新的选择集
Set adSS = ThisDrawing.SelectionSets.Add("adSS")
If Err Then Set adSS = ThisDrawing.SelectionSets.Add("adSS")
adSS.Clear

'指定过滤机制
fType(0) = 0: fData(0) = "TEXT"
fType(0) = 8: fData(1) = "*"    '图层名
adSS.Select acSelectionSetAll, , , fType, fData
'对单行文字完成多重文字替换
For Each adText In adSS
    With adText
    '使用instr函数判断是否包含所要查找的字符串(如果不包含返回0)
    If InStr(.TextString, Misc1) Then .TextString = replaceStr(.TextString, Misc1, MiscReplace1, False)
    If Misc2 <> "" Then
        If InStr(.TextString, Misc2) Then .TextString = replaceStr(.TextString, Misc2, MiscReplace2, False)
    End If
    If Misc3 <> "" Then
        If InStr(.TextString, Misc3) Then .TextString = replaceStr(.TextString, Misc3, MiscReplace3, False)
    End If
    End With
Next adText

adSS.Clear
fType(0) = 0: fData(0) = "MTEXT"
fType(1) = 8: fData(1) = "*"
adSS.Select acSelectionSetAll, , , fType, fData
'对多行文字完成多重文字替换
For Each adMText In adSS
    With adMText
        If InStr(.TextString, Misc1) Then .TextString = replaceStr(.TextString, Misc1, MiscReplace1, False)
        If Misc2 <> "" Then
            If InStr(.TextString, Misc2) Then .TextString = replaceStr(.TextString, Misc2, MiscReplace2, False)
        End If
        If Misc3 <> "" Then
            If InStr(.TextString, Misc3) Then .TextString = replaceStr(.TextString, Misc3, MiscReplace2, False)
        End If
    End With
Next adMText
adSS.Delete
ThisDrawing.Regen acAllViewports
'结束后退出程序
Unload Me
End Sub

Private Sub cmdCancel_Click()
End
End Sub

Attribute VB_Name = "模块1"


Public Function replaceStr(ByVal searchStr As String, ByVal oldStr As String, ByVal newStr As String, ByVal firstOnly As Boolean) As String
'对错误操作的处理
If searchStr = "" Then Exit Function
If oldStr = "" Then Exit Function

replaceStr = ""
Dim i As Integer, oldStrLen As String, holdStr As String, StrLoc As Integer
'计算原来字符串的长度
oldStrLen = Len(oldStr)
StrLoc = InStr(searchStr, oldStr)
While StrLoc > 0
'获得图形中文字对象位于查找字符串之前的字符串
holdstrr = holdStr & Left(searchStr, StrLoc - 1) & newStr
'获得图形中文字对象位于查找字符串之后的字符串
searchStr = Mid(searchStr, StrLoc + oldStrLen)
StrLoc = InStr(searchStr, oldStr)
If firstOnly Then replaceStr = holdStr & searchStr: Exit Function
Wend
replaceStr = holdStr & searchStr
End Function
