Attribute VB_Name = "模块1"

Public Sub First()
'创建在实例中使用的对象
Dim pt1(2) As Double
Dim pt2(2) As Double
Dim pt3(2) As Double
Dim pt4(2) As Double
Dim pt5(2) As Double
Dim objLine As AcadLine
Dim objCir As AcadCircle
Dim objArc As AcadArc

pt1(0) = 0: pt1(1) = 0: pt1(2) = 0
pt2(0) = 5: pt2(1) = 8: pt2(2) = 0
pt3(0) = 10: pt3(1) = 0: pt3(2) = 0
pt4(0) = 15: pt4(1) = 8: pt4(2) = 0
pt5(0) = 20: pt5(1) = 0: pt5(2) = 0


'圆形
Set objCir = ThisDrawing.ModelSpace.AddCircle(pt1, 1)
ThisDrawing.ModelSpace.AddCircle pt3, 3
ThisDrawing.ModelSpace.AddCircle pt5, 5

'直线
Set objLine = ThisDrawing.ModelSpace.AddLine(pt1, pt2)
ThisDrawing.ModelSpace.AddLine pt4, pt5

'圆弧
Set objArc = AddArc3Pt(pt1, pt3, pt4)

On Error Resume Next
Dim SSet As AcadSelectionSet
If Not IsNull(ThisDrawing.SelectionSets.Item("example")) Then
    Set SSet = ThisDrawing.SelectionSets.Item("example")
    SSet.Erase
End If
Set SSet = ThisDrawing.SelectionSets.Add("example")

Dim FilterType(4) As Integer
Dim FilterData(4) As Variant
FilterType(0) = -4
FilterData(0) = "<or" '逻辑运算符的开始，表示一个或多个运算对象
FilterType(1) = 0
FilterData(1) = "Arc"
FilterType(2) = 0
FilterData(2) = "Circle"
FilterType(3) = 0
FilterData(3) = "Eillipse"
FilterType(4) = -4
FilterData(4) = "or>" '逻辑运算结束

SSet.Select acSelectionSetCrossing, pt1, pt4, FilterType, FilterData

Dim element As AcadEntity
For Each element In SSet
    If element.ObjectName = "AcDbCircle" Or element.EntityType = acArc Then
    element.Color = acRed
    End If
Next

End Sub

Attribute VB_Name = "模块2"
Public Function AddArc3Pt(ByVal ptSt As Variant, ByVal ptSc As Variant, ByVal ptEn As Variant) As AcadArc
Dim objArc As AcadArc
Dim ptCen As Variant
Dim radius As Double
ptCen = GetCenOf3Pt(ptSt, ptSc, ptEn, radius)
Set objArc = AddArcCSEP(ptCen, ptSt, ptEn)
objArc.Color = acGreen
objArc.Update
Set AddArc3Pt = objArc
End Function
Public Function GetCenOf3Pt(pt1 As Variant, pt2 As Variant, pt3 As Variant, ByRef radius As Double) As Variant
Dim xysm, xyse, xy As Double
Dim ptCen(2) As Double
xy = pt1(0) ^ 2 + pt1(1) ^ 2
xyse = xy - pt3(0) ^ 2 - pt3(1) ^ 2
xysm = sy - pt2(0) ^ 2 - pt2(1) ^ 2
xy = (pt1(0) - pt2(0)) * (pt1(1) - pt3(1)) - (pt1(0) - pt3(0)) * (pt1(1) - pt2(1))

If Abs(xy) < 0.0000001 Then
    MsgBox "无法创建圆形"
    Exit Function
End If
ptCen(0) = (xysm * (pt1(1) - pt3(1)) - xyse * (pt1(1) - pt2(1))) / (2 * xy)
ptCen(1) = (xyse * (pt1(0) - pt2(0)) - xysm * (pt1(0) - pt3(0))) / (2 * xy)
ptCen(2) = 0
radius = Sqr((pt1(0) - ptCen(0)) * (pt1(0) - ptCen(0)) + (pt1(1) - ptCen(1)) * (pt1(1) - ptCen(1)))
If radius < 0.0000001 Then
    MsgBox "半径过小"
    Exit Function
End If
GetCenOf3Pt = ptCen
End Function
Public Function AddArcCSEP(ByVal ptCen As Variant, ByVal ptSt As Variant, ByVal ptEn As Variant) As AcadArc
Dim objArc As AcadArc
Dim radius As Double
Dim stAng As Double
Dim enAng As Double
radius = GetDistance(ptCen, ptSt)
stAng = ThisDrawing.Utility.AngleFromXAxis(ptCen, ptSt)
enAng = ThisDrawing.Utility.AngleFromXAxis(ptCen, ptEn)
Set objArc = ThisDrawing.ModelSpace.AddArc(ptCen, radius, stAng, enAng)
objArc.Color = acCyan
objArc.Update
Set AddArcCSEP = objArc
End Function
Public Function GetDistance(ByVal sp As Variant, ByVal ep As Variant) As Double
Dim x, y, z As Double
x = sp(0) - ep(0)
y = sp(1) - ep(1)
z = sp(2) - ep(2)
GetDistance = Sqr((x ^ 2) + (y ^ 2) + (z ^ 2))
End Function
