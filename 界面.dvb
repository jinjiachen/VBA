Attribute VB_Name = "Form1"
Attribute VB_Base = "0{44119409-39CB-4368-BA7A-8E79E5DB3048}{40697362-1E81-4AE3-9F4C-F1A9426B4F74}"
Attribute VB_GlobalNameSpace = False
Attribute VB_Creatable = False
Attribute VB_PredeclaredId = True
Attribute VB_Exposed = False
Attribute VB_TemplateDerived = False
Attribute VB_Customizable = False
Private Sub CommandButton4_Click()

End Sub

Private Sub cmdColor_Click()
On Error Resume Next
With comDLG
    .DialogTitle = "选择字体颜色"
    .ShowColor
End With
txtFile.ForeColor = comDLG.Color
End Sub

Private Sub cmdExit_Click()
Unload Me
End Sub

Private Sub cmdFonts_Click()
On Error Resume Next
With comDLG
    .Flags = cdlCFBoth + cdlCFEffects
    .ShowFont
End With
txtFile.Font = comDLG.FONTNAME
End Sub

Private Sub cmdOpen_Click()
On Error Resume Next
With comDLG
    .DialogTitle = "选择文本文件"
    .Filter = "文本文件(*.txt)|*.txt|所有文件(*.*)|*.*"
    .InitDir = "c:\"
    .ShowOpen
End With
If Right(comDLG.FileName, 3) <> "txt" Then
    MsgBox "不支持的格式", vbCritical, "警告"
Exit Sub
End If
Open comDLG.FileName For Input As #1
txtFile.Text = StrConv(InputB$(LOF(1), 1), vbUnicode)
Close #1

End Sub

Private Sub cmdSave_Click()
On Error Resume Next
With comDLG
    .DialogTitle = "保存文本文件"
    .Filter = "文本文件(*.txt) | *.txt | 所有文件(*.*) | *.*"
    .InitDir = "c:\"
    .DefaultExt = "txt"
    .ShowSave
End With
Open comDLG.FileName For Output As #1
Print #1, txtFile.Text
Close 1
End Sub

Attribute VB_Name = "ThisDrawing"
Attribute VB_Base = "0{D70E31AD-2614-49F2-B0FC-ACA781D81F3E}"
Attribute VB_GlobalNameSpace = False
Attribute VB_Creatable = False
Attribute VB_PredeclaredId = True
Attribute VB_Exposed = True
Attribute VB_TemplateDerived = False
Attribute VB_Customizable = True

Public Sub TestLine()
Dim ptST(0 To 2) As Double
Dim ptEN(0 To 2) As Double
ptST(0) = 100: ptST(1) = 100: ptST(2) = 0
ptEN(0) = 150: ptEN(1) = 100: ptEN(2) = 0
'1
AddLine ptST, ptEN
'2
AddLineXY 100, 120, 150, 120
'3
AddLineReXY ptST, 50, 50
'4
AddLineReAL ptST, 3, 50

End Sub

Attribute VB_Name = "frmMain"
Attribute VB_Base = "0{8795615F-F4D7-489B-AA31-7262B00D7AB1}{26540BA6-0131-4429-AF21-4A2244B4A8F8}"
Attribute VB_GlobalNameSpace = False
Attribute VB_Creatable = False
Attribute VB_PredeclaredId = True
Attribute VB_Exposed = False
Attribute VB_TemplateDerived = False
Attribute VB_Customizable = False
Private Sub cmdGetInt_Click()
Dim i As Integer
frmMain.Hide
i = ThisDrawing.Utility.GetInteger
tbInteger = i
frmMain.Show
End Sub

Private Sub cmdPickAng_Click()
Dim angle As Double
frmMain.Hide
angle = ThisDrawing.Utility.GetAngle(, "指定角度:")
angle = 180 * angle / 3.1415926
tbAngle = Round(angle, 2)
frmMain.Show

End Sub

Private Sub cmdPickPT_Click()
Dim ptPick As Variant
frmMain.Hide
ptPick = ThisDrawing.Utility.GetPoint(, "指定点;")
tbPtX = ptPick(0)
tbPtY = ptPick(1)
tbPtZ = ptPick(2)
frmMain.Show

End Sub

Private Sub CommandButton1_Click()
Dim keyWord As String
ThisDrawing.Utility.InitializeUserInput 0, "L C A"
frmMain.Hide
keyWord = ThisDrawing.Utility.GetKeyword(vbCrLf & "输入选项[直线(L)/圆(C)]<弧度(A)>:")
If keyWord = "" Then keyWord = "A"
MsgBox "你选择的关键字是" & keyWord, , "获利关键字"
frmMain.Show



End Sub

Private Sub CommandButton2_Click()
End
End Sub

Private Sub Label1_Click()

End Sub

Private Sub Label7_Click()

End Sub

Attribute VB_Name = "模块1"
Option Explicit
Public Sub alternation()
frmMain.Show
End Sub

Attribute VB_Name = "模块2"
Option Explicit
Public Sub comDialog()
Form1.Show
End Sub

Attribute VB_Name = "模块3"

Public Function AddLine(ByVal ptST As Variant, ByVal ptEN As Variant) As AcadLine
Set AddLine = ThisDrawing.ModelSpace.AddLine(ptST, ptEN)
End Function

Public Function AddLineXY(ByVal x1 As Double, ByVal y1 As Double, ByVal x2 As Double, ByVal y2 As Double) As AcadLine
Dim pt1(2) As Double
Dim pt2(2) As Double
pt1(0) = x1: pt1(1) = y1: pt1(2) = 0
pt2(0) = x2: pt2(1) = y2: pt2(2) = 0
Set AddLineXY = AddLine(pt1, pt2)
End Function

Public Function AddLineReXY(ByVal ptST As Variant, ByVal x As Double, ByVal y As Double) As AcadLine
Dim ptEN As Variant
ptEN = GetPoint(ptST, x, y)
Set AddLineReXY = AddLine(ptST, ptEN)
End Function

Public Function GetPoint(ByVal pt As Variant, ByVal x As Double, ByVal y As Double) As Variant
Dim ptTarget(2) As Double
ptTarget(0) = pt(0) + x
ptTarget(1) = pt(1) + y
ptTarget(2) = 0
GetPoint = ptTarget
End Function

Public Function AddLineReAL(ByVal ptST As Variant, ByVal angle As Double, ByVal length As Double) As AcadLine
Dim ptEN As Variant
ptEN = GetPointAR(ptST, angle, length)
Set AddLineReAL = AddLine(ptST, ptEN)
End Function

Public Function GetPointAR(ByVal ptBase As Variant, ByVal angle As Double, ByVal length As Double) As Variant
Dim pt(0 To 2) As Double
pt(0) = ptBase(0) + length * Cos(angle)
pt(1) = ptBase(0) + length * Sin(angle)
pt(2) = ptBase(2)
GetPointAR = pt
End Function
